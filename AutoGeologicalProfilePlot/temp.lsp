(defun c:remove-last-point ( / __strata_index.int)
	(setq *section_points_x* (cdr *section_points_x*))
	(setq *ground_points* (cdr *ground_points*))
  (setq __strata_index.int  0)
  (while (< __strata_index.int *strata_count)
    (set (read (strcat "*strata_points_" (itoa __strata_index.int) "*"))
     		 (cdr (eval (read (strcat "*strata_points_" (itoa __strata_index.int) "*")))))
  	(setq __strata_index.int (1+ __strata_index.int)) 
  )
)
