(defun load_menu_template (self.dcl_id.int / __set_all_key_value __action_tile_to_function __run_function_by_dialog_id __load_menu_window __dcl_key_list.list __dialog_return_id.int __dialog_name.str __key.str __dcl_key.str)         
	(defun __set_all_key_value ( / __dcl_key.str )                  
		(foreach __dcl_key.str __dcl_key_list.list
			(set (read (strcat "*" __dcl_key.str "_value*")) (get_tile __dcl_key.str))
		)
	)
  
	(defun __action_tile_to_function (self.recv_key.str)                                                                       
		(cond
			((= self.recv_key.str "cancel")            
				(done_dialog 0)
			)
			((= self.recv_key.str "accept")            
				(__set_all_key_value)
				(done_dialog 1)
			)
			((= self.recv_key.str "help")            
				(__set_all_key_value)
				(done_dialog 2)
			)
			((= self.recv_key.str "其它的KEY值，根据情况改")
				(__set_all_key_value)
				(done_dialog 3)
			)
		)
	)
	(defun __run_function_by_dialog_id (self.recv_dialog_id.int / __ss_length.int)                    
		(cond
			((= self.recv_dialog_id.int 0)
       
			)
		)
	)
	(defun send_global_value ()                                                  
		                                                  
	)
	(defun __load_menu_window (self.recv_dcl_id.int / )         
		(setq __dialog_return_id.int 2 __dialog_name.str "输入对话框名称")
		(setq __dcl_key_list.list '("输入需要key，组成列表"))
		(while (> __dialog_return_id.int 1)                                              
			(if (not (new_dialog __dialog_name.str self.recv_dcl_id.int)) (exit))
			(foreach __key.str __dcl_key_list.list
				(if (eval (read (strcat "*" __key.str "_value*")))
					(set_tile __key.str (eval (read (strcat "*" __key.str "_value*"))))
					(set (read (strcat "*" __key.str "_value*")) "NULL")
				)         
				(action_tile __key.str "(__action_tile_to_function $key)")         
			)
			(setq __dialog_return_id.int (start_dialog))
			(__run_function_by_dialog_id __dialog_return_id.int)
		)
		(unload_dialog self.recv_dcl_id.int)
	)
  (__load_menu_window self.dcl_id.int)
)
